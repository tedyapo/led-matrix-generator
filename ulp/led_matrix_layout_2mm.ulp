//
// layout & route (rows x cols) matrix of 0603 LEDs
//

if (schematic) {
	dlgMessageBox("This ULP must be run in board view.");
	exit("");
}
// parameters and defaults
int rows = 8;
int cols = 16;
int reflector = 1; // flag for drawing silkscreen reflector (0, 1)

if (argc >= 3){
	// allow override of size from command 
	rows = strtod(argv[1]);
	cols = strtod(argv[2]);
	reflector = strtod(argv[3]);
}

// string buffer and output variable
string s;
string command = "";

// load design rule changes specific to this pattern and merge them
string ULPPath(){
	string ulp_path;
	char bkslash = '/'; // always use '/' as path delimiter to keep ULPs platform-independent
	int pos = strrchr(argv[0], bkslash);
	if (pos >= 0) {            // split path from filename
	   ulp_path = strsub(argv[0], 0, pos + 1);
	   }
	return(ulp_path);
}

string dru_filename = ULPPath() + "/../dru/led_matrix_layout_2mm.dru"; 
sprintf(s, "DRC MERGE %s;\n", dru_filename);
command += s;

// setup commands
string grid_units[] = { "MIC", "MM", "MIL", "INCH" };
sprintf(s, "GRID %s;\n", grid_units[1]); // all dimensions below are given in: MM
command += s;
command += "LAYER TSTOP; GRID ON LINES; GRID 1.0;\n";

// via drill/dia size
string via_shapes[] = { "SQUARE", "ROUND", "OCTAGON", "LONG", "OFFSET" };
string via_shape = via_shapes[1];
real annular_ring = 0.15;
real via_drill = 0.3;
real via_diameter = via_drill + 2 * annular_ring;

sprintf(s, "SET DRILL %f;\n", via_drill);
command += s;

// via offsets
real via_x_origin = 0.25;
real via_y_origin = -0.5;

// trace width
real width = 0.4;

// LED spacing
real x_pitch = 2.0;
real y_pitch = 2.0;

// header spacing adjustments
real x_header_offset = -2.0;
real y_header_offset = -2.0;

// LED pad offset (dependent on LED package)
real x_pad_offset = 0.5; // TODO: switch to evaluating actual offsets depending on the chosen package 
real y_pad_offset = 0.5; // see : https://github.com/plusea/EAGLE/blob/master/ulp/smd-coordinate.ulp#L63-L99

// origin offset
real x_origin = 8;
real y_origin = 8;


// place all LEDs
for (int row = 0; row < rows; row++){
  for (int col = 0; col < cols; col++){
    
    // place LED
    string s;
    real x = x_origin + col * x_pitch;
    real y = y_origin + row * y_pitch;
    sprintf(s, "MOVE 'LED_%d_%d' (%f %f);\n",
            row, col, x, y);
    command += s;

    // set LED rotation to 45 degrees absolute
    sprintf(s, "ROTATE =R45 'LED_%d_%d';\n",
            row, col);
    command += s;

    // set bend to start-45-horizontal-end
    command += "SET WIRE_BEND 3;\n";
   
    // place column via
    sprintf(s, "VIA 'COL%d' %f %s (%f %f);\n",
            col,
            via_diameter,
            via_shape,
            x + via_x_origin,
            y + via_y_origin);
    command += s;
    
    // route row trace (top)
    sprintf(s, "LAYER 1; WIRE 'ROW%d' %f (%f %f) (%f %f);\n",
            row,
            width,
            x + x_pad_offset - x_pitch,
            y + y_pad_offset,
            x + x_pad_offset,
            y + y_pad_offset);
    command += s;

    // route col trace (bottom)
    sprintf(s, "LAYER %d; WIRE 'COL%d' %f (%f %f) (%f %f);\n",
            row == 0 ? 1 : 16,
            col,
            width,
            x + via_x_origin,
            y + via_y_origin,
            x + via_x_origin,
            y + via_y_origin - y_pitch);                        
    command += s;

    // route col trace (top)
    sprintf(s, "LAYER 1; WIRE 'COL%d' %f (%f %f) (%f %f);\n",
            col,
            width,
            x - x_pad_offset,
            y - y_pad_offset,
            x + via_x_origin,
            y + via_y_origin);                        
    command += s;

  }
}


// place row resistors
for (row = 0; row < rows; row++){
  real x = x_origin - 0.5 * x_pitch + x_header_offset;
  real y = y_origin + row * y_pitch;
  sprintf(s, "MOVE 'R_ROW_%d' (%f %f);\n",
          row, x, y);
  command += s;
  sprintf(s, "ROTATE =R0 'R_ROW_%d';\n",
          row);
  command += s;
}

// place row headers
for (row = 0; row < rows; row++){
  real x = x_origin - 2 * x_pitch + x_header_offset;
  real y = y_origin + row * y_pitch;
  sprintf(s, "MOVE 'HDR_ROW_%d' (%f %f);\n",
          row, x, y);
  command += s;
  // extend trace

  sprintf(s, "LAYER 1; WIRE 'ROW_IN_%d' %f (%f %f) (%f %f);\n",
          row,
          width,
          x,
          y,
          x + 2.0,
          y);
  command += s;
}

// place col resistors
for (int col = 0; col < cols; col++){
  real x = x_origin + col * x_pitch;
  real y = y_origin - 0.5 * y_pitch + y_header_offset;
  sprintf(s, "MOVE 'R_COL_%d' (%f %f);\n",
          col, x, y);
  command += s;
  sprintf(s, "ROTATE =R90 'R_COL_%d';\n",
          col);
  command += s;
}

// place col headers
for (col = 0; col < cols; col++){
  real x = x_origin + col * x_pitch;
  real y = y_origin - 2 * y_pitch + y_header_offset;
  sprintf(s, "MOVE 'HDR_COL_%d' (%f %f);\n",
          col, x, y);
  command += s;
  // extend trace
  sprintf(s, "LAYER 1; WIRE 'COL_IN_%d' %f (%f %f) (%f %f);\n",
          col,
          width,
          x,
          y,
          x,
          y + 2.0);   
		  
  command += s;
}

// execute all the commands
exit(command);
