//
// create schematic with rows x cols matrix of LEDs
//

if (board) {
	exit("RUN led_matrix_layout.ulp;\n");
}

// parameters and defaults
int rows = 8;
int cols = 16;

string packages[] = {"LED_0603"};
int packageIdx = 0;

string headers[] = {"PIN_HDR254", "PIN_HDR200"};
int headerIdx = 0;

int runSettingsDlg(){
	int l;
	int Result = dlgDialog("LED Matrix Parameters") {
		string slist[];
		dlgStretch(0);
		dlgLabel("Number Of Rows");
		dlgIntEdit(rows, 1, 4096);
		dlgLabel("Number Of Columns");
		dlgIntEdit(cols, 1, 4096);
		dlgLabel("LED Package");
		dlgComboBox(packages, packageIdx);
		dlgLabel("Header Type");
		dlgComboBox(headers, headerIdx);
		dlgStretch(1);
		dlgHBoxLayout {
			dlgStretch(0);
			dlgPushButton("+&OK") dlgAccept();
			dlgStretch(1);
			dlgPushButton("-&Cancel") dlgReject();
			dlgStretch(0);
		}
		dlgStretch(0);
	};
	return Result;
}

if (argc >= 3){
	// allow override of size from command 
	rows = strtod(argv[1]);
	cols = strtod(argv[2]);
} else if (runSettingsDlg() == 0){
	exit (0);
}

// LED symbol spacing
real x_pitch = 0.3;
real y_pitch = 0.3;

// origin offset
real x_offset = 0.3;
real y_offset = 0.3;

string command = "";

// ensure led_matrix.lbr is being used
string ULPPath(){
	string ulp_path;
	char bkslash = '/'; // always use '/' as path delimiter to keep ULPs platform-independent
	int pos = strrchr(argv[0], bkslash);
	if (pos >= 0) {            // split path from filename
	   ulp_path = strsub(argv[0], 0, pos + 1);
	   }
	return(ulp_path);
}

string lbr_filename = ULPPath() + "/../library/led_matrix.lbr"; 
command += "USE '" + lbr_filename + "';\n";

// add LEDs and connecting wires
for (int row = 0; row < rows; row++){
  for (int col = 0; col < cols; col++){
    
    // place LED
    string s;
    real x = x_offset + col * x_pitch;
    real y = y_offset + row * y_pitch;
    sprintf(s, "ADD %s@led_matrix.lbr 'LED_%d_%d' (%f %f);\n",
	        packages[packageIdx],
            row, col, x, y);
    command += s;

    // add row net
    sprintf(s, "NET 'ROW%d' (%f %f) (%f %f);\n",
            row,
            x - 0.4,
            y + 0.1,
            x + 0.1,
            y + 0.1);
    command += s;

    // add col net
    sprintf(s, "NET 'COL%d' (%f %f) (%f %f);\n",
            col,
            x - 0.1,
            y - 0.4,
            x - 0.1,
            y - 0.1);
    command += s;

    // add junctions
    sprintf(s, "JUNCTION (%f %f) ;\n",
            x - 0.1,
            y - 0.1);
    command += s;
    sprintf(s, "JUNCTION (%f %f) ;\n",
            x + 0.1,
            y + 0.1);
    command += s;
  }
}

// add row resistors
for (row = 0; row < rows; row++){
  string s;
  real x = x_offset - 2*x_pitch - 0.2;
  real y = y_offset + row * y_pitch + 0.1;
  sprintf(s, "ADD R0805@led_matrix.lbr 'R_ROW_%d' R90 (%f %f);\n",
          row, x, y);
  command += s;  
}

// add row headers
for (row = 0; row < rows; row++){
  string s;
  real x = x_offset - 2*x_pitch - 0.8;
  real y = y_offset + row * y_pitch + 0.1;
  sprintf(s, "ADD %s@led_matrix.lbr 'HDR_ROW_%d' R180 (%f %f);\n",
          headers[headerIdx],
          row, x, y);
  command += s;  
}

// add col resistors
for (int col = 0; col < cols; col++){
  string s;
  real x = x_offset + col * x_pitch - 0.1;
  real y = y_offset - 2 * y_pitch - 0.2;
  sprintf(s, "ADD R0805@led_matrix.lbr 'R_COL_%d' R180 (%f %f);\n",
          col, x, y);
  command += s;  
}

// add col headers
for (col = 0; col < cols; col++){
  string s;
  real x = x_offset + col * x_pitch - 0.1;
  real y = y_offset - 2 * y_pitch - 0.8;
  sprintf(s, "ADD %s@led_matrix.lbr 'HDR_COL_%d' R270 (%f %f);\n",
          headers[headerIdx],
          col, x, y);
  command += s;  
}

exit(command);
