//
// layout & route (rows x cols) matrix of 0603 LEDs
//

if (schematic) {
	exit("RUN led_matrix_schematic.ulp;\n");
}

// parameters and defaults
int rows = 8;
int cols = 16;
int reflector = 1; // flag for drawing silkscreen reflector (0, 1)

int patternIdx;
string patternNames[] = {
	"2.54 mm classic",
	"2.0 mm compact" };
string patternCmds[] = {
	"RUN led_matrix_layout_100mil.ulp %d %d %d",
	"RUN led_matrix_layout_2mm.ulp %d %d %d" };
	
int runSettingsDlg(){
	int l;
	int Result = dlgDialog("LED Matrix Parameters") {
		string slist[];
		dlgStretch(0);
		dlgLabel("Number Of Rows");
		dlgIntEdit(rows, 1, 4096);
		dlgLabel("Number Of Columns");
		dlgIntEdit(cols, 1, 4096);
		dlgLabel("Layout Pattern");
		dlgComboBox(patternNames, patternIdx);
		dlgLabel("Reflector Background");
		string reflectorOpts[] = {"Off", "On"};
		dlgComboBox(reflectorOpts, reflector);
		dlgStretch(1);
		dlgHBoxLayout {
			dlgStretch(0);
			dlgPushButton("+&OK") dlgAccept();
			dlgStretch(1);
			dlgPushButton("-&Cancel") dlgReject();
			dlgStretch(0);
		}
		dlgStretch(0);
	};
	return Result;
}

if (runSettingsDlg() == 0){
	exit (0);
}

string command;
string cmdbuf;

// ensure led_matrix.lbr is being used
string ULPPath(){
	string ulp_path;
	char bkslash = '/'; // always use '/' as path delimiter to keep ULPs platform-independent
	int pos = strrchr(argv[0], bkslash);
	if (pos >= 0) {            // split path from filename
	   ulp_path = strsub(argv[0], 0, pos + 1);
	   }
	return(ulp_path);
}

string lbr_filename = ULPPath() + "/../library/led_matrix.lbr"; 
command += "USE '" + lbr_filename + "';\n";

// run selected pattern script
sprintf(cmdbuf, patternCmds[patternIdx], rows, cols, reflector);
command += cmdbuf;

exit(command);
